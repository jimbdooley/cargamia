import sys, runpy
import FreeCAD as App
import FreeCADGui

PROJECT = r"C:\Users\james\Documents\misc_projects\cargamia"
if True: # linux
    PROJECT = r"/home/james/Documents/misc_projects/cargamia"

scripts = [
    r"/v2_pillar.py",
    r"/v2_octo.py",
    r"/v2_centrack_dub_right.py",
    r"/v2_s_curve.py",
    r"/v3_straight_right.py",
    r"/v3_click_track.py",
    r"/v4_short_bridge.py",
    r"/v4_right_bridge.py",
    r"/v5_start_dub_right.py",
]
SCRIPT = PROJECT + scripts[8]

sys.path.insert(0, PROJECT)
for name, mod in list(sys.modules.items()):
    if (getattr(mod, "__file__", None) or "").startswith(PROJECT):
        del sys.modules[name]

res = runpy.run_path(
    SCRIPT, 
    init_globals={
        "__makeMold__": False, 
        "__for3DPrint__": False,
        "__useCache__": True,
    },
    run_name="__main__"
)

Part.show(res["rtnPart"])
for optPart in ["octoA", "octoB"]:
    if optPart in res:
        
        Part.show(res[optPart])

App.ActiveDocument.recompute()

FreeCADGui.ActiveDocument = FreeCADGui.getDocument(res["docName"]) 
App.setActiveDocument(res["docName"])
FreeCADGui.ActiveDocument.ActiveView.fitAll()
